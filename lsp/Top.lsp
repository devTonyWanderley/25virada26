;;;	--NOTAS--
;;;		->existe um bug quando se faz arestas a partir de duas arestas existentes
;;;		->no sistema:
;;;			->elabora/descerver fluxo de trabalho do usuário	..	..	ok
;;;		->no lsp:
;;;			->lançar pontos criando layer por atributo	..	..	..	ok
;;;			->desenhar contorno	..
;;;				->carregar eventuais contornos existentes no desenho	..	ok
;;;				->importar arquivo con e atribuir um nome	..	..	ok
;;;				->importar pontos	..	..	..	..	..	ok
;;;			->carregar variável de lista de superfícies
;;;		->no cpp:
;;;			->análise e bem provável reformulação desde as classes de tipos, passando pela interface e modulação do programa

;;;	--FLUXO DE TRABALHO DO USUÁRIO--
;;;		->ler pontos do dxf fornecido pela Leica e gerar o pnt	..	..	..	..	..	..	..	c++
;;;		->lançar pontos no desenho auxiliar de superfície primitiva	..	..	..	..	..	..	lsp	..	desenho 1
;;;		->fazer malha no desenho auxiliar de superfície primitiva	..	..	..	..	..	..	lsp	..	desenho 1
;;;		->exportar pontos (novo pnt) e malha da primitiva	..	..	..	..	..	..	..	lsp	..	desenho 1
;;;		->importar pontos e malha	..	..	..	..	..	..	..	..	..	..	c++
;;;		->gerar superfície primitiva, incluindo seu contorno	..	..	..	..	..	..	..	c++
;;;		->exportar a primitiva com seu contorno	..	..	..	..	..	..	..	..	..	c++
;;;		->importar pontos (layer por atributo) e primitiva em desenho auxiliar para projetar traçado(s)	..	..	lsp	..	desenho 2
;;;			->talvez projetar os traçados e seções no passo 3. Não estou inclinado a isso
;;;		->esboçar traçados e seções da primitiva em planta	..	..	..	..	..	..	..	lsp	..	desenho 2
;;;		->exportar esboço de traçados e seções da primitiva em planta	..	..	..	..	..	..	lsp	..	desenho 2
;;;		->importar superfície primitiva e esboço do traçado	..	..	..	..	..	..	..	c++
;;;		->criar detalhamento do(s) traçado(s) em planta, perfil e seções	..	..	..	..	..	c++
;;;		->exportar detalhamento prévio do traçado	..	..	..	..	..	..	..	..	c++
;;;		->importar primitiva + detalhamento prévio do traçado	..	..	..	..	..	..	..	lsp	..	desenho 3
;;;		->fazer ajustes finais e imprimir ou rever etapas anteriores	..	..	..	..	..	..	lsp/cad	..	desenho 3

;;;	--HEAD--
(setq #param-leitura '(("PONTO" "Abrir arquivo de pontos" "C:/2025/Soft/IL2/" "pnt")
		       ("ARESTA" "Abrir arquivo de arestas" "C:/2025/Soft/IL2/" "ars")
		       ("FACE" "Abrir arquivo de faces" "C:/2025/Soft/IL2/" "sup")
		       ("CONTORNO" "Abrir arquivo de faces" "C:/2025/Soft/IL2/" "con")
		       )
      #param-export '(("PONTO" "Salvar arquivo de pontos" "C:/2025/Soft/IL2/" "pnt")
		      ("ARESTA" "Salvar arquivo de arestas" "C:/2025/Soft/IL2/" "ars")
		      ("FACE" "Salvar arquivo de faces" "C:/2025/Soft/IL2/" "sup")
		      ("CONTORNO" "Abrir arquivo de faces" "C:/2025/Soft/IL2/" "con")
		      )
      #param-desenho '(("PONTO" "_Pontos" 0.1)
		       ("ARESTA" "_Arestas")
		       ("FACE" "_Faces")
		       ("CONTORNO" "_Contornos")
		       )
      )

;;;	--ROTINAS--
;;;		--INICIALIZAÇÃO--
(defun top:inicia(/ i)
  (while (nth (setq i (if i (1+ i) 0)) #param-leitura)
    (regapp (car (nth i #param-leitura)))
    )
  (princ "\nEventuais repetições no desenho:\n\tPontos:")
  (setq #pontos (top:ler-pontos-do-desenho))
  (princ "\n\n\tArestas:")
  (setq #arestas (top:ler-arestas-do-desenho))
  (princ "\n\n\tContornos:")
  (setq #contornos (top:ler-contornos-do-desenho))
  (princ "\n\nTOP carregado com sucesso")
  )

;;;		--I/O--
;;;			--MANIPULAR TEXTO--
(defun top:norma_tx(arg / c r)
  (setq r "")
  (while (/= (setq c (substr arg 1 1) arg (substr arg 2) c c) "")
    (if (or (wcmatch c "@") (wcmatch c "#"))
      (setq r (strcat r c))
      )
    )
  r
  )

(defun top:ler-ln-ponto(arg / r)
  (setq r (list (+ (atof (substr arg 38 4)) (/ (atof (substr arg 43 3)) 1000.0)))
	r (cons (+ (atof (substr arg 27 7)) (/ (atof (substr arg 35 3)) 1000.0)) r)
	r (cons (+ (atof (substr arg 17 7)) (/ (atof (substr arg 24 3)) 1000.0)) r)
	r (cons (top:norma_tx (substr arg 9 8)) r)
	r (cons (top:norma_tx (substr arg 1 8)) r)
	)
  )

(defun top:ler-ln-contorno(arg / i r)
  (while (nth (setq i (if i (1+ i) 0)) arg)
    (setq r (cons (top:norma_tx (nth i arg)) r))
    )
  (reverse r)
  )

(defun top:preenche-texto-na-cabeça(tx ch tam)
  (while (< (strlen tx) tam)
    (setq tx (strcat ch tx))
    )
  tx
  )

(defun top:preenche-texto-na-cauda(tx ch tam)
  (while (< (strlen tx) tam)
    (setq tx (strcat tx ch))
    )
  tx
  )

(defun top:preenche-num-3dec(num tam)
  (setq num (rtos num 2 3))
  (if (null (wcmatch num "*`.*"))
    (setq num (strcat num "."))
    )
  (while (null (wcmatch num "*`.???"))
    (setq num (top:preenche-texto-na-cauda num "0" (+ 1 (strlen num))))
    )
  (setq num (top:preenche-texto-na-cabeça num "0" tam))
  num
  )

(defun top:ln-ponto-export(arg / id atr x y z)
  (setq id (top:preenche-texto-na-cabeça (car arg) " " 8)
	atr (top:preenche-texto-na-cabeça (cadr arg) " " 8)
	x (top:preenche-num-3dec (car (last arg)) 10)
	y (top:preenche-num-3dec (cadr (last arg)) 11)
	z (top:preenche-num-3dec (caddr (last arg)) 8)
	)
  (strcat id atr x y z)
  )

(defun top:ln-aresta-export(arg)
  (strcat (top:preenche-texto-na-cabeça (car arg) " " 8) (top:preenche-texto-na-cabeça (cadr arg) " " 8))
  )

;;;			--ARQUIVO--
(defun top:get_na(msg dir ex f) (getfiled msg dir ex f))

(defun top:ler-arquivo(chave / na pa ln lt)
  (if (setq na (top:get_na
		 (cadr (assoc chave #param-leitura))
		 (caddr (assoc chave #param-leitura))
		 (nth 3 (assoc chave #param-leitura))
		 0
		 )
	    )
    (if (setq pa (open na "r"))
      (progn
	(while (setq ln (read-line pa))
	  (setq lt (cons ln lt))
	  )
	(setq pa (close pa))
	)
      (princ "erro no arquivo\n")
      )
    (princ "erro no nome do arquivo\n")
    )
  (if lt
    (reverse lt)
    (princ)
    )
  )

(defun top:exportar-arquivo(chave lt / na pa i)
  (if (setq na (top:get_na
		 (cadr (assoc chave #param-leitura))
		 (caddr (assoc chave #param-leitura))
		 (nth 3 (assoc chave #param-leitura))
		 1
		 )
	    )
    (if (setq pa (open na "w"))
      (progn
	(while (nth (setq i (if i (1+ i) 0)) lt)
	  (write-line (nth i lt) pa)
	  )
	(setq pa (close pa))
	)
      (princ "erro no arquivo\n")
      )
    (princ "erro no nome do arquivo\n")
    )
  )

;;;			--DESENHO--
(defun top:ler-xdata(en)
  (if (setq en (assoc -3
		      (if (listp en)
			(if (= (type (car en)) 'ename)
			  (entget (car en) (mapcar 'car #param-leitura))
			  en
			  )
			(entget en (mapcar 'car #param-leitura))
			)
		      )
	    )
    (mapcar 'cdr (cdadr en))
    )
  )

(defun top:tipo-de-xdata(en)
  (if (setq en (assoc -3
		      (if (listp en)
			(if (= (type (car en)) 'ename)
			  (entget (car en) (mapcar 'car #param-leitura))
			  en
			  )
			(entget en (mapcar 'car #param-leitura))
			)
		      )
	    )
    (caadr en)
    )
  )

(defun top:elimina-repetição(arg / r)
  (while (cdr arg)
    (progn
      (if (null (member (car arg) (cdr arg)))
	(setq r (cons (car arg) r))
	(print (car arg))
	)
      (setq arg (cdr arg))
      )
    )
  (cons (car arg) r)
  )

(defun top:varre-xdata(tipo / en len)
  (while (setq en (if en (entnext en) (entnext)))
    (if (= (top:tipo-de-xdata en) tipo)
      (setq len (cons (top:ler-xdata en) len))
      )
    )
  (top:elimina-repetição len)
  )

(defun top:ler-pontos-do-desenho(/ a)
  (if (car (setq a (top:varre-xdata "PONTO")))
    (setq #pontos a)
    (setq #pontos nil)
    )
  )

(defun top:ler-arestas-do-desenho(/ a)
  (if (car (setq a (top:varre-xdata "ARESTA")))
    (setq #arestas a)
    (setq #arestas nil)
    )
  )

(defun top:ler-contornos-do-desenho(/ a)
  (if (car (setq a (top:varre-xdata "CONTORNO")))
    (setq #contornos a)
    (setq #contornos nil)
    )
  )

(defun top:select-pra-aresta(/ n en lt)
  (while (< (setq n (if n n 0)) 6)
    (if (setq en (entsel "\nSelecione"))
      (if (= (top:tipo-de-xdata en) "PONTO")
	(setq n (+ n 2)
	      lt (cons (top:ler-xdata en) lt)
	      )
	(if (= (top:tipo-de-xdata en) "ARESTA")
	  (setq n (+ n 2)
		lt (cons (top:ler-xdata en) lt)
		)
	  )
	)
      (setq n (+ n 7))
      )
    )
  lt
  )

;;;		--DESENHAR--
(defun top:faz-point(arg la 3d)
  (entmake (list (cons 0 "POINT") (cons 8 la)
		 (list 10 (nth 2 arg) (nth 3 arg) (if 3d (nth 4 arg) 0.0))
		 (list -3
		       (list "PONTO"
			     (cons 1000 (car arg))
			     (cons 1000 (cadr arg))
			     (cons 1010 (cddr arg))
			     )
		       )
		 )
	   )
  )

(defun top:mostra-cotas-e-atrs(/ lt i x y h tx)
  (if (setq lt (top:varre-xdata "PONTO"))
    (while (nth (setq i (if i (1+ i) 0)) lt)
      (progn
	(setq x (+ (car (last (nth i lt))) (* (caddr (assoc "PONTO" #param-desenho)) 0.7))
	      y (- (cadr (last (nth i lt))) (* (caddr (assoc "PONTO" #param-desenho)) 2.5))
	      h (* 1.5 (caddr (assoc "PONTO" #param-desenho)))
	      tx (rtos (last (last (nth i lt))) 2 3)
	      )
	(entmake (list (cons 0 "TEXT") (cons 8 "_Cotas") (list 10 x y 0.0) (cons 40 h) (cons 1 tx)))
	(setq y (+ y (* (caddr (assoc "PONTO" #param-desenho)) 1.75))
	      tx (car (nth i lt))
	      )
	(entmake (list (cons 0 "TEXT") (cons 8 "_Nomes") (list 10 x y 0.0) (cons 40 h) (cons 1 tx)))
	(setq y (+ y (* (caddr (assoc "PONTO" #param-desenho)) 1.75))
	      tx (cadr (nth i lt))
	      )
	(entmake (list (cons 0 "TEXT") (cons 8 "_Atributos") (list 10 x y 0.0) (cons 40 h) (cons 1 tx)))
	)
      )
    )
  (princ)
  )

(defun top:faz-aresta(p0 p1 / p)
  (if (> (last (last p0)) (last (last p1))) (setq p p0 p0 p1 p1 p))
  (entmake (list (cons 0 "LINE") (cons 8 "_Arestas")
		 (cons 10 (reverse (cons 0.0 (cdr (reverse (last p0))))))
		 (cons 11 (reverse (cons 0.0 (cdr (reverse (last p1))))))
		 (list -3 (list "ARESTA" (cons 1000 (car p0)) (cons 1000 (car p1))))
		 )
	   )
  (princ)
  )

(defun top:faz-arestas(arg / a b c d)
  (if (> (length arg) 1)
    (if (< (length arg) 3)	;	2 elementos
      (if (> (length (car arg)) 2)	;	2e & (p, ?)
	(if (> (length (cadr arg)) 2)	;	2e & (p, p)
	  (top:faz-aresta (car arg) (cadr arg))
	  (progn	;	2e & (p, a)
	    (top:faz-aresta (car arg) (assoc (car (cadr arg)) #pontos))
	    (top:faz-aresta (car arg) (assoc (cadr (cadr arg)) #pontos))
	    )
	  )
	(if (> (length (cadr arg)) 2)	;	2e & (a, p)
	  (progn
	    (top:faz-aresta (assoc (car (car arg)) #pontos) (cadr arg))
	    (top:faz-aresta (assoc (cadr (car arg)) #pontos) (cadr arg))
	    )
	  (progn	;	2e & (a, a)
	    (setq a (assoc (car (car arg)) #pontos)
		  b (assoc (cadr (car arg)) #pontos)
		  c (assoc (car (cadr arg)) #pontos)
		  d (assoc (cadr (cadr arg)) #pontos)
		  )
	    (if (inters (last a) (last c) (last b) (last d))
	      (progn
		(top:faz-aresta a c)
		(top:faz-aresta b c)
		(top:faz-aresta a d)
		)
	      (progn
		(top:faz-aresta a c)
		(top:faz-aresta b d)
		(top:faz-aresta a d)
		)
	      )
	    )
	  )
	)
      (if (> (length (car arg)) 2)	;	3e & (p, ?, ?)
	(if (> (length (cadr arg)) 2)	;	3e & (p, p, ?)
	   (if (> (length (caddr arg)) 2)	;	3e & (p, p, p)
	     (progn
	       (top:faz-aresta (car arg) (cadr arg))
	       (top:faz-aresta (car arg) (caddr arg))
	       (top:faz-aresta (cadr arg) (caddr arg))
	       )
	     (progn	;	3e & (p, p, a)
	       (setq a (car arg)
		     b (cadr arg)
		     c (assoc (car (caddr arg)) #pontos)
		     d (assoc (cadr (caddr arg)) #pontos)
		     )
	       (if (inters (reverse (cdr (reverse (last a))))
			   (reverse (cdr (reverse (last b))))
			   (reverse (cdr (reverse (last c))))
			   (reverse (cdr (reverse (last d))))
			   )
		 (progn
		   (top:faz-aresta a c)
		   (top:faz-aresta a d)
		   (top:faz-aresta b c)
		   (top:faz-aresta b d)
		   )
		 (progn
		   (top:faz-aresta a b)
		   (top:faz-aresta a c)
		   (top:faz-aresta a d)
		   (if (inters (reverse (cdr (reverse (last a))))
			       (reverse (cdr (reverse (last c))))
			       (reverse (cdr (reverse (last b))))
			       (reverse (cdr (reverse (last d))))
			       )
		     (top:faz-aresta b c)
		     (top:faz-aresta b d)
		     )
		   )
		 )
	       )
	     )
	  (progn	;	3e & (p, a, p)
	    (setq a (car arg)
		  b (caddr arg)
		  c (assoc (car (cadr arg)) #pontos)
		  d (assoc (cadr (cadr arg)) #pontos)
		  )
	    (if (inters (reverse (cdr (reverse (last a))))
			(reverse (cdr (reverse (last b))))
			(reverse (cdr (reverse (last c))))
			(reverse (cdr (reverse (last d))))
			)
	      (progn
		(top:faz-aresta a c)
		(top:faz-aresta a d)
		(top:faz-aresta b c)
		(top:faz-aresta b d)
		)
	      (progn
		(top:faz-aresta a b)
		(top:faz-aresta a c)
		(top:faz-aresta a d)
		(if (inters (reverse (cdr (reverse (last a))))
			    (reverse (cdr (reverse (last c))))
			    (reverse (cdr (reverse (last b))))
			    (reverse (cdr (reverse (last d))))
			    )
		  (top:faz-aresta b c)
		  (top:faz-aresta b d)
		  )
		)
	      )
	    )
	  )
	(progn	;	3e & (a, p, p)
	  (setq a (cadr arg)
		b (caddr arg)
		c (assoc (car (car arg)) #pontos)
		d (assoc (cadr (car arg)) #pontos)
		)
	  (if (inters (reverse (cdr (reverse (last a))))
		      (reverse (cdr (reverse (last b))))
		      (reverse (cdr (reverse (last c))))
		      (reverse (cdr (reverse (last d))))
		      )
	    (progn
	      (top:faz-aresta a c)
	      (top:faz-aresta a d)
	      (top:faz-aresta b c)
	      (top:faz-aresta b d)
	      )
	    (progn
	      (top:faz-aresta a b)
	      (top:faz-aresta a c)
	      (top:faz-aresta a d)
	      (if (inters (reverse (cdr (reverse (last a))))
			  (reverse (cdr (reverse (last c))))
			  (reverse (cdr (reverse (last b))))
			  (reverse (cdr (reverse (last d))))
			  )
		(top:faz-aresta b c)
		(top:faz-aresta b d)
		)
	      )
	    )
	  )
	)
      )
    )
  )

(defun top:desenha-contorno(arg / i lxd lp lt a)
  (while (nth (setq i (if i (1+ i) 0)) arg)
    (progn
      (setq lxd (cons (cons 1000 (nth i arg)) lxd))
      (if (> i 0)
	(setq a (assoc (nth i arg) #pontos)
	      lp (cons (list 10 (nth 2 a) (nth 3 a)) lp)
	      )
	)
      )
    )
  (setq lxd (list -3 (cons "CONTORNO" (reverse lxd)))
	lt (list (cons 0 "LWPOLYLINE")
		 (cons 100 "AcDbEntity")
		 (cons 8 (strcat "_" (car arg)))
		 (cons 100 "AcDbPolyline")
		 (cons 90 (length lp))
		 (cons 70 1)
		 (cons 43 0.0)
		 (cons 38 0.0)
		 (cons 39 0.0)
		 )
	arg nil
	i nil
	)
  (while (nth (setq i (if i (1+ i) 0)) lp)
    (setq arg (append
		(list
		  (nth i lp)
		  (cons 40 0.0)
		  (cons 41 0.0)
		  (cons 42 0.0)
		  (cons 91 0)
		  )
		arg
		)
	  )
    )
  (setq lt (append lt arg))
  (entmake (append lt (list lxd)))
  )

;;;	--INTERMEDIÁRIOS DE CHAMADAS--
(defun top:lança-pontos(3d / lt i)
  (setvar "pdmode" 35)
  (setvar "pdsize" (caddr (assoc "PONTO" #param-desenho)))
  (if (setq lt (top:ler-arquivo "PONTO"))
    (while (nth (setq i (if i (1+ i) 0)) lt)
      (top:faz-point (top:ler-ln-ponto (nth i lt)) (cadr (assoc "PONTO" #param-desenho)) 3d)
      )
    (princ "erro ao lançar pontos")
    )
  (top:ler-pontos-do-desenho)
  (top:ler-arestas-do-desenho)
  (princ)
  )

(defun top:lança-pontos-por-atr(3d / lt i a)
  (setvar "pdmode" 35)
  (setvar "pdsize" (caddr (assoc "PONTO" #param-desenho)))
  (if (setq lt (top:ler-arquivo "PONTO"))
    (while (nth (setq i (if i (1+ i) 0)) lt)
      (setq a (top:ler-ln-ponto (nth i lt))
	    a (top:faz-point a (strcat "_" (cadr a)) 3d)
	    )
      )
    (princ "erro ao lançar pontos")
    )
  (top:ler-pontos-do-desenho)
  (princ)
  )

;;;	--CHAMADAS--
(defun c:teste_lsp(/ lt i)
  (while (setq lt (top:select-pra-aresta))
    (top:faz-arestas lt)
    )
  )

(defun c:lança-pontos-2d()(top:lança-pontos nil))
  
(defun c:lança-pontos-3d()(top:lança-pontos 't))

(defun c:lança-pontos-atr-2d()(top:lança-pontos-por-atr nil))
  
(defun c:lança-pontos-atr-3d()(top:lança-pontos-por-atr 't))
  
(defun c:cotas-e-atributos()(top:mostra-cotas-e-atrs))
  
(defun c:faz-arestas(/ lt)
  (while (setq lt (top:select-pra-aresta))
    (top:faz-arestas lt)
    )
  (princ)
  )

(defun c:exporta-pontos()
  (top:ler-pontos-do-desenho)
  (top:exportar-arquivo "PONTO" (mapcar 'top:ln-ponto-export #pontos))
  (princ)
  )

(defun c:exporta-arestas()
  (top:ler-arestas-do-desenho)
  (top:exportar-arquivo "ARESTA" (mapcar 'top:ln-aresta-export #arestas))
  (princ)
  )

(defun c:importar-contorno(/ id lt)
  (if (/= (setq id (getstring "Nome do contorno")) "")
    (if (setq lt (top:ler-arquivo "CONTORNO"))
      (setq lt (top:ler-ln-contorno lt)
	    #contornos (cons (cons id lt) #contornos)
	    )
      )
    (alert "cancelado")
    )
  (princ)
  )

(defun c:importar-pontos-append(/ lt)
  (if (setq lt (top:ler-arquivo "PONTO"))
    (if (setq lt (mapcar 'top:ler-ln-ponto lt))
      (setq #pontos (append lt #pontos))
      )
    )
  (if #pontos (setq #pontos (top:elimina-repetição #pontos)))
  (princ)
  )

(defun c:desenhar-contorno(/ n)
  (if #pontos
    (if #contornos
      (progn
	(if (> (length #contornos) 1)
	  (alert "criar rotina pra escolher o contorno a desenhar\natravez do n")
	  (setq n 0)
	  )
	(if n (top:desenha-contorno (nth n #contornos)))
	)
      (alert "#contornos vazia")
      )
    (alert "#pontos vazia")
    )
  (princ)
  )

(top:inicia)

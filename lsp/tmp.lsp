;;;	--HEAD--
(setq #param-leitura '(("PONTO" "Abrir arquivo de pontos" "C:/2025/Soft/InstLocal/" "txt")
		       ("ARESTA" "Abrir arquivo de arestas" "C:/2025/Soft/InstLocal/" "txt")
		       ("FACE" "Abrir arquivo de faces" "C:/2025/Soft/InstLocal/" "txt")
		       )
      #param-export '(("PONTO" "Salvar arquivo de pontos" "C:/2025/Soft/InstLocal/" "txt")
		      ("ARESTA" "Salvar arquivo de arestas" "C:/2025/Soft/InstLocal/" "txt")
		      ("FACE" "Salvar arquivo de faces" "C:/2025/Soft/InstLocal/" "txt")
		      )
      #param-desenho '(("PONTO" "_Pontos" 0.1)
		       ("ARESTA" "_Arestas")
		       ("FACE" "_Faces")
		       )
      )

;;;	--ROTINAS--
;;;		--INICIALIZAÇÃO--
(defun top:inicia(/ i)
  (while (nth (setq i (if i (1+ i) 0)) #param-leitura)
    (regapp (car (nth i #param-leitura)))
    )
  (setq #pontos (top:ler-pontos-do-desenho))
  (setq #arestas (top:ler-arestas-do-desenho))
  (princ "TMP carregado com sucesso")
  )

;;;		--I/O--
;;;			--MANIPULAR TEXTO--
(defun top:norma_tx(arg / c r)
  (setq r "")
  (while (/= (setq c (substr arg 1 1) arg (substr arg 2) c c) "")
    (if (or (wcmatch c "@") (wcmatch c "#"))
      (setq r (strcat r c))
      )
    )
  r
  )

(defun top:ler-ln-ponto(arg / r)
  (setq r (list (+ (atof (substr arg 38 4)) (/ (atof (substr arg 43 3)) 1000.0)))
	r (cons (+ (atof (substr arg 27 7)) (/ (atof (substr arg 35 3)) 1000.0)) r)
	r (cons (+ (atof (substr arg 17 7)) (/ (atof (substr arg 24 3)) 1000.0)) r)
	r (cons (top:norma_tx (substr arg 9 8)) r)
	r (cons (top:norma_tx (substr arg 1 8)) r)
	)
  )

(defun top:preenche-texto-na-cabeça(tx ch tam)
  (while (< (strlen tx) tam)
    (setq tx (strcat ch tx))
    )
  tx
  )

(defun top:preenche-texto-na-cauda(tx ch tam)
  (while (< (strlen tx) tam)
    (setq tx (strcat tx ch))
    )
  tx
  )

(defun top:preenche-num-3dec(num tam)
  (setq num (rtos num 2 3))
  (if (null (wcmatch num "*`.*"))
    (setq num (strcat num "."))
    )
  (while (null (wcmatch num "*`.???"))
    (setq num (top:preenche-texto-na-cauda num "0" (+ 1 (strlen num))))
    )
  (setq num (top:preenche-texto-na-cabeça num "0" tam))
  num
  )

(defun top:ln-ponto-export(arg / id atr x y z)
  (setq id (top:preenche-texto-na-cabeça (car arg) " " 8)
	atr (top:preenche-texto-na-cabeça (cadr arg) " " 8)
	x (top:preenche-num-3dec (car (last arg)) 10)
	y (top:preenche-num-3dec (cadr (last arg)) 11)
	z (top:preenche-num-3dec (caddr (last arg)) 8)
	)
  (strcat id atr x y z)
  )

(defun top:ln-aresta-export(arg)
  (strcat (top:preenche-texto-na-cabeça (car arg) " " 8) (top:preenche-texto-na-cabeça (cadr arg) " " 8))
  )

;;;			--ARQUIVO--
(defun top:get_na(msg dir ex f) (getfiled msg dir ex f))

(defun top:ler-arquivo(chave / na pa ln lt)
  (if (setq na (top:get_na
		 (cadr (assoc chave #param-leitura))
		 (caddr (assoc chave #param-leitura))
		 (nth 3 (assoc chave #param-leitura))
		 0
		 )
	    )
    (if (setq pa (open na "r"))
      (progn
	(while (setq ln (read-line pa))
	  (setq lt (cons ln lt))
	  )
	(setq pa (close pa))
	)
      (princ "erro no arquivo\n")
      )
    (princ "erro no nome do arquivo\n")
    )
  (if lt
    (reverse lt)
    (princ)
    )
  )

(defun top:exportar-arquivo(chave lt / na pa i)
  (if (setq na (top:get_na
		 (cadr (assoc chave #param-leitura))
		 (caddr (assoc chave #param-leitura))
		 (nth 3 (assoc chave #param-leitura))
		 1
		 )
	    )
    (if (setq pa (open na "w"))
      (progn
	(while (nth (setq i (if i (1+ i) 0)) lt)
	  (write-line (nth i lt) pa)
	  )
	(setq pa (close pa))
	)
      (princ "erro no arquivo\n")
      )
    (princ "erro no nome do arquivo\n")
    )
  )

;;;			--DESENHO--
(defun top:ler-xdata(en)
  (if (setq en (assoc -3
		      (if (listp en)
			(if (= (type (car en)) 'ename)
			  (entget (car en) (mapcar 'car #param-leitura))
			  en
			  )
			(entget en (mapcar 'car #param-leitura))
			)
		      )
	    )
    (mapcar 'cdr (cdadr en))
    )
  )

(defun top:tipo-de-xdata(en)
  (if (setq en (assoc -3
		      (if (listp en)
			(if (= (type (car en)) 'ename)
			  (entget (car en) (mapcar 'car #param-leitura))
			  en
			  )
			(entget en (mapcar 'car #param-leitura))
			)
		      )
	    )
    (caadr en)
    )
  )

(defun top:varre-xdata(tipo / en len)
  (while (setq en (if en (entnext en) (entnext)))
    (if (= (top:tipo-de-xdata en) tipo)
      (setq len (cons (top:ler-xdata en) len))
      )
    )
  (reverse len)
  )

(defun top:ler-pontos-do-desenho() (setq #pontos (top:varre-xdata "PONTO")))

(defun top:ler-arestas-do-desenho() (setq #arestas (top:varre-xdata "ARESTA")))

(defun top:select-pra-aresta(/ n en lt)
  (while (< (setq n (if n n 0)) 6)
    (if (setq en (entsel "\nSelecione"))
      (if (= (top:tipo-de-xdata en) "PONTO")
	(setq n (+ n 2)
	      lt (cons (top:ler-xdata en) lt)
	      )
	(if (= (top:tipo-de-xdata en) "ARESTA")
	  (setq n (+ n 2)
		lt (cons (top:ler-xdata en) lt)
		)
	  )
	)
      (setq n (+ n 7))
      )
    )
  lt
  )

;;;		--DESENHAR--
(defun top:faz-point(arg la 3d)
  (entmake (list (cons 0 "POINT") (cons 8 la)
		 (list 10 (nth 2 arg) (nth 3 arg) (if 3d (nth 4 arg) 0.0))
		 (list -3
		       (list "PONTO"
			     (cons 1000 (car arg))
			     (cons 1000 (cadr arg))
			     (cons 1010 (cddr arg))
			     )
		       )
		 )
	   )
  )

(defun top:mostra-cotas-e-atrs(/ lt i x y h tx)
  (if (setq lt (top:varre-xdata "PONTO"))
    (while (nth (setq i (if i (1+ i) 0)) lt)
      (progn
	(setq x (car (last (nth i lt)))
	      y (- (cadr (last (nth i lt))) (* (caddr (assoc "PONTO" #param-desenho)) 2.5))
	      h (* 1.5 (caddr (assoc "PONTO" #param-desenho)))
	      tx (rtos (last (last (nth i lt))) 2 3)
	      )
	(entmake (list (cons 0 "TEXT") (cons 8 "_Cotas") (list 10 x y 0.0) (cons 40 h) (cons 1 tx)))
	(setq y (+ y (* (caddr (assoc "PONTO" #param-desenho)) 3.5))
	      tx (cadr (nth i lt))
	      )
	(entmake (list (cons 0 "TEXT") (cons 8 "_Atributos") (list 10 x y 0.0) (cons 40 h) (cons 1 tx)))
	)
      )
    )
  (princ)
  )

(defun top:faz-aresta(p0 p1 / p)
  (if (> (last (last p0)) (last (last p1))) (setq p p0 p0 p1 p1 p))
  (entmake (list (cons 0 "LINE") (cons 8 "_Arestas")
		 (cons 10 (reverse (cons 0.0 (cdr (reverse (last p0))))))
		 (cons 11 (reverse (cons 0.0 (cdr (reverse (last p1))))))
		 (list -3 (list "ARESTA" (cons 1000 (car p0)) (cons 1000 (car p1))))
		 )
	   )
  (princ)
  )

(defun top:faz-arestas(arg / a b c d)
  (if (> (length arg) 1)
    (if (< (length arg) 3)	;	2 elementos
      (if (> (length (car arg)) 2)	;	2e & (p, ?)
	(if (> (length (cadr arg)) 2)	;	2e & (p, p)
	  (top:faz-aresta (car arg) (cadr arg))
	  (progn	;	2e & (p, a)
	    (top:faz-aresta (car arg) (assoc (car (cadr arg)) #pontos))
	    (top:faz-aresta (car arg) (assoc (cadr (cadr arg)) #pontos))
	    )
	  )
	(if (> (length (cadr arg)) 2)	;	2e & (a, p)
	  (progn
	    (top:faz-aresta (assoc (car (car arg)) #pontos) (cadr arg))
	    (top:faz-aresta (assoc (cadr (car arg)) #pontos) (cadr arg))
	    )
	  (progn	;	2e & (a, a)
	    (setq a (assoc (car (car arg)) #pontos)
		  b (assoc (cadr (car arg)) #pontos)
		  c (assoc (car (cadr arg)) #pontos)
		  d (assoc (cadr (cadr arg)) #pontos)
		  )
	    (if (inters (last a) (last c) (last b) (last d))
	      (progn
		(top:faz-aresta a c)
		(top:faz-aresta b c)
		(top:faz-aresta a d)
		)
	      (progn
		(top:faz-aresta a c)
		(top:faz-aresta b d)
		(top:faz-aresta a d)
		)
	      )
	    )
	  )
	)
      (if (> (length (car arg)) 2)	;	3e & (p, ?, ?)
	(if (> (length (cadr arg)) 2)	;	3e & (p, p, ?)
	   (if (> (length (caddr arg)) 2)	;	3e & (p, p, p)
	     (progn
	       (top:faz-aresta (car arg) (cadr arg))
	       (top:faz-aresta (car arg) (caddr arg))
	       (top:faz-aresta (cadr arg) (caddr arg))
	       )
	     (progn	;	3e & (p, p, a)
	       (setq a (car arg)
		     b (cadr arg)
		     c (assoc (car (caddr arg)) #pontos)
		     d (assoc (cadr (caddr arg)) #pontos)
		     )
	       (if (inters (reverse (cdr (reverse (last a))))
			   (reverse (cdr (reverse (last b))))
			   (reverse (cdr (reverse (last c))))
			   (reverse (cdr (reverse (last d))))
			   )
		 (progn
		   (top:faz-aresta a c)
		   (top:faz-aresta a d)
		   (top:faz-aresta b c)
		   (top:faz-aresta b d)
		   )
		 (progn
		   (top:faz-aresta a b)
		   (top:faz-aresta a c)
		   (top:faz-aresta a d)
		   (if (inters (reverse (cdr (reverse (last a))))
			       (reverse (cdr (reverse (last c))))
			       (reverse (cdr (reverse (last b))))
			       (reverse (cdr (reverse (last d))))
			       )
		     (top:faz-aresta b c)
		     (top:faz-aresta b d)
		     )
		   )
		 )
	       )
	     )
	  (progn	;	3e & (p, a, p)
	    (setq a (car arg)
		  b (caddr arg)
		  c (assoc (car (cadr arg)) #pontos)
		  d (assoc (cadr (cadr arg)) #pontos)
		  )
	    (if (inters (reverse (cdr (reverse (last a))))
			(reverse (cdr (reverse (last b))))
			(reverse (cdr (reverse (last c))))
			(reverse (cdr (reverse (last d))))
			)
	      (progn
		(top:faz-aresta a c)
		(top:faz-aresta a d)
		(top:faz-aresta b c)
		(top:faz-aresta b d)
		)
	      (progn
		(top:faz-aresta a b)
		(top:faz-aresta a c)
		(top:faz-aresta a d)
		(if (inters (reverse (cdr (reverse (last a))))
			    (reverse (cdr (reverse (last c))))
			    (reverse (cdr (reverse (last b))))
			    (reverse (cdr (reverse (last d))))
			    )
		  (top:faz-aresta b c)
		  (top:faz-aresta b d)
		  )
		)
	      )
	    )
	  )
	(progn	;	3e & (a, p, p)
	  (setq a (cadr arg)
		b (caddr arg)
		c (assoc (car (car arg)) #pontos)
		d (assoc (cadr (car arg)) #pontos)
		)
	  (if (inters (reverse (cdr (reverse (last a))))
		      (reverse (cdr (reverse (last b))))
		      (reverse (cdr (reverse (last c))))
		      (reverse (cdr (reverse (last d))))
		      )
	    (progn
	      (top:faz-aresta a c)
	      (top:faz-aresta a d)
	      (top:faz-aresta b c)
	      (top:faz-aresta b d)
	      )
	    (progn
	      (top:faz-aresta a b)
	      (top:faz-aresta a c)
	      (top:faz-aresta a d)
	      (if (inters (reverse (cdr (reverse (last a))))
			  (reverse (cdr (reverse (last c))))
			  (reverse (cdr (reverse (last b))))
			  (reverse (cdr (reverse (last d))))
			  )
		(top:faz-aresta b c)
		(top:faz-aresta b d)
		)
	      )
	    )
	  )
	)
      )
    )
  )

;;;	--INTERMEDIÁRIOS DE CHAMADAS--
(defun top:lança-pontos(3d / lt i)
  (setvar "pdmode" 35)
  (setvar "pdsize" (caddr (assoc "PONTO" #param-desenho)))
  (if (setq lt (top:ler-arquivo "PONTO"))
    (while (nth (setq i (if i (1+ i) 0)) lt)
      (top:faz-point (top:ler-ln-ponto (nth i lt)) (cadr (assoc "PONTO" #param-desenho)) 3d)
      )
    (princ "erro ao lançar pontos")
    )
  (top:ler-pontos-do-desenho)
  (top:ler-arestas-do-desenho)
  (princ)
  )

;;;	--CHAMADAS--
(defun c:teste_lsp(/ lt i)
  (while (setq lt (top:select-pra-aresta))
    (top:faz-arestas lt)
    )
  )

(defun c:lança-pontos-2d()(top:lança-pontos nil))
  
(defun c:lança-pontos-3d()(top:lança-pontos 't))
  
(defun c:cotas-e-atributos()(top:mostra-cotas-e-atrs))
  
(defun c:faz-arestas(/ lt)
  (while (setq lt (top:select-pra-aresta))
    (top:faz-arestas lt)
    )
  (princ)
  )

(defun c:exporta-pontos()
  (top:ler-pontos-do-desenho)
  (top:exportar-arquivo "PONTO" (mapcar 'top:ln-ponto-export #pontos))
  (princ)
  )

(defun c:exporta-arestas()
  (top:ler-arestas-do-desenho)
  (top:exportar-arquivo "ARESTA" (mapcar 'top:ln-aresta-export #arestas))
  (princ)
  )

(top:inicia)
